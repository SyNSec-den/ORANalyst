-- ASN1START
-- **************************************************************
--
-- Constant definitions
--
-- **************************************************************

E2AP-Constants {
iso(1) identified-organization(3) dod(6) internet(1) private(4) enterprise(1) 53148 e2(1) version2 (2) e2ap(1) e2ap-Constants (4) }

DEFINITIONS AUTOMATIC TAGS ::= 

BEGIN

IMPORTS
	ProcedureCode,
	ProtocolIE-ID
FROM E2AP-CommonDataTypes;

-- **************************************************************
--
-- Elementary Procedures
-- 
-- **************************************************************
id-E2setup									ProcedureCode ::= 1
id-ErrorIndication							ProcedureCode ::= 2
id-Reset									ProcedureCode ::= 3
id-RICcontrol								ProcedureCode ::= 4
id-RICindication							ProcedureCode ::= 5
id-RICserviceQuery							ProcedureCode ::= 6
id-RICserviceUpdate							ProcedureCode ::= 7
id-RICsubscription							ProcedureCode ::= 8
id-RICsubscriptionDelete					ProcedureCode ::= 9
id-E2nodeConfigurationUpdate				ProcedureCode ::= 10
id-E2connectionUpdate						ProcedureCode ::= 11
id-RICsubscriptionDeleteRequired			ProcedureCode ::= 12

-- **************************************************************
--
-- Extension constants
--
-- **************************************************************

maxProtocolIEs								INTEGER ::= 65535


-- **************************************************************
--
-- Lists
-- 
-- **************************************************************
maxnoofErrors								INTEGER ::= 256
maxofE2nodeComponents						INTEGER ::= 1024
maxofRANfunctionID							INTEGER ::= 256
maxofRICactionID							INTEGER ::= 16
maxofTNLA									INTEGER ::= 32
maxofRICrequestID							INTEGER ::= 4294967295


-- **************************************************************
--
-- IEs
-- 
-- **************************************************************
id-Cause									ProtocolIE-ID ::= 1
id-CriticalityDiagnostics					ProtocolIE-ID ::= 2
id-GlobalE2node-ID							ProtocolIE-ID ::= 3
id-GlobalRIC-ID								ProtocolIE-ID ::= 4
id-RANfunctionID   							ProtocolIE-ID ::= 5
id-RANfunctionID-Item   					ProtocolIE-ID ::= 6
id-RANfunctionIEcause-Item					ProtocolIE-ID ::= 7
id-RANfunction-Item							ProtocolIE-ID ::= 8
id-RANfunctionsAccepted						ProtocolIE-ID ::= 9
id-RANfunctionsAdded						ProtocolIE-ID ::= 10
id-RANfunctionsDeleted						ProtocolIE-ID ::= 11
id-RANfunctionsModified						ProtocolIE-ID ::= 12
id-RANfunctionsRejected						ProtocolIE-ID ::= 13
id-RICaction-Admitted-Item					ProtocolIE-ID ::= 14
id-RICactionID								ProtocolIE-ID ::= 15
id-RICaction-NotAdmitted-Item				ProtocolIE-ID ::= 16
id-RICactions-Admitted						ProtocolIE-ID ::= 17
id-RICactions-NotAdmitted					ProtocolIE-ID ::= 18
id-RICaction-ToBeSetup-Item					ProtocolIE-ID ::= 19
id-RICcallProcessID							ProtocolIE-ID ::= 20
id-RICcontrolAckRequest						ProtocolIE-ID ::= 21
id-RICcontrolHeader							ProtocolIE-ID ::= 22
id-RICcontrolMessage						ProtocolIE-ID ::= 23
id-RICcontrolStatus							ProtocolIE-ID ::= 24
id-RICindicationHeader						ProtocolIE-ID ::= 25
id-RICindicationMessage						ProtocolIE-ID ::= 26
id-RICindicationSN							ProtocolIE-ID ::= 27
id-RICindicationType						ProtocolIE-ID ::= 28
id-RICrequestID								ProtocolIE-ID ::= 29
id-RICsubscriptionDetails					ProtocolIE-ID ::= 30
id-TimeToWait								ProtocolIE-ID ::= 31
id-RICcontrolOutcome						ProtocolIE-ID ::= 32
id-E2nodeComponentConfigUpdate				ProtocolIE-ID ::= 33
id-E2nodeComponentConfigUpdate-Item			ProtocolIE-ID ::= 34
id-E2nodeComponentConfigUpdateAck			ProtocolIE-ID ::= 35
id-E2nodeComponentConfigUpdateAck-Item		ProtocolIE-ID ::= 36
id-E2connectionSetup						ProtocolIE-ID ::= 39
id-E2connectionSetupFailed					ProtocolIE-ID ::= 40
id-E2connectionSetupFailed-Item				ProtocolIE-ID ::= 41
id-E2connectionFailed-Item					ProtocolIE-ID ::= 42
id-E2connectionUpdate-Item					ProtocolIE-ID ::= 43
id-E2connectionUpdateAdd					ProtocolIE-ID ::= 44
id-E2connectionUpdateModify					ProtocolIE-ID ::= 45
id-E2connectionUpdateRemove					ProtocolIE-ID ::= 46
id-E2connectionUpdateRemove-Item			ProtocolIE-ID ::= 47
id-TNLinformation							ProtocolIE-ID ::= 48
id-TransactionID							ProtocolIE-ID ::= 49
id-E2nodeComponentConfigAddition			ProtocolIE-ID ::= 50
id-E2nodeComponentConfigAddition-Item		ProtocolIE-ID ::= 51
id-E2nodeComponentConfigAdditionAck			ProtocolIE-ID ::= 52
id-E2nodeComponentConfigAdditionAck-Item	ProtocolIE-ID ::= 53
id-E2nodeComponentConfigRemoval				ProtocolIE-ID ::= 54
id-E2nodeComponentConfigRemoval-Item		ProtocolIE-ID ::= 55
id-E2nodeComponentConfigRemovalAck			ProtocolIE-ID ::= 56
id-E2nodeComponentConfigRemovalAck-Item		ProtocolIE-ID ::= 57
id-E2nodeTNLassociationRemoval				ProtocolIE-ID ::= 58
id-E2nodeTNLassociationRemoval-Item			ProtocolIE-ID ::= 59
id-RICsubscriptionToBeRemoved				ProtocolIE-ID ::= 50
id-RICsubscription-withCause-Item			ProtocolIE-ID ::= 51

END
-- ASN1STOP
